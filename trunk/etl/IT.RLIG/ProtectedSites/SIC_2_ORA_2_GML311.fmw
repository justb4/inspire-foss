FME workspace SIC_2_ORA_2_GML311.fmw

Parameters:
- DestDataset_GML = SIC_GML311.gml   # Destination Geography Markup Language (GML) File
- SourceDataset_ORACLE8I = AMB_DB_SIT   # Source Oracle Spatial Object Service

Readers:
- ORACLE8I_1: ORACLE8I from $(SourceDataset_ORACLE8I) in MonteMario_1.Italy-1_GRID

Writers:
- GML_1: GML to $(DestDataset_GML) in EPSG:4258

CTEMI.PS_SIC (reader ORACLE8I_1)
    attributes: ID char(12), NOME_SITO char(100), SUPERFICIE_HA float, PERIMETRO_KM float, LEGAL_FOUNDATION_DOC_TITLE char(100), LEGAL_FOUNDATION_DOC_DATE date, LEGAL_FOUNDATION_DATE date
    -> Joiner
Joiner
    __WB_ADDED_FIELDS = CLASSIFICATION
    __WB_CARDINALITY = 1:M
    __WB_CACHE_SIZE = 5000
    __WB_ODBC_TABLE = CTEMI.V_PS_SIC_CLASSIFICATION
    __WB_ODBC_PASSWORD = TEMIC
    __WB_LIST_NAME = siteClassificationList
    __WB_ODBC_SOURCE = AMB_DB_SIT
    __WB_TRIM_KEYS = No
    __WB_ODBC_USER_NAME = CTEMI
    __WB_TABLE_FIELDS = ID_SIC,CLASSIFICATION,CLASSIFICAZIONE
    __WB_SERVER_TYPE = ORACLE8I
    __WB_KEY_FIELDS = ID_SIC,ID
    JOINED -> Joiner_2
Joiner_2
    __WB_ADDED_FIELDS = DESIGNATION,DESIGNATION_SCHEMA,PERCENTUALE
    __WB_CARDINALITY = 1:M
    __WB_CACHE_SIZE = 5000
    __WB_ODBC_TABLE = CTEMI.V_PS_SIC_DESIGNATION
    __WB_ODBC_PASSWORD = TEMIC
    __WB_LIST_NAME = siteDesignationList
    __WB_ODBC_SOURCE = AMB_DB_SIT
    __WB_TRIM_KEYS = No
    __WB_ODBC_USER_NAME = CTEMI
    __WB_TABLE_FIELDS = ID_SIC,DESIGNATION_SCHEMA,DESIGNATION,DESIGNAZIONE,PERCENTUALE
    __WB_SERVER_TYPE = ORACLE8I
    __WB_KEY_FIELDS = ID_SIC,ID
    JOINED -> AttributeExposer
AttributeExposer
    ATTR_LIST = applicationSchema,idNameSpace
    -> applicationSchemaSetter
applicationSchemaSetter: AttributeSetter
    VAL = simple
    DEST_ATTR = &applicationSchema
    -> idNameSpaceSetter
idNameSpaceSetter: AttributeSetter
    VAL = IT.RLIG.SIC
    DEST_ATTR = &idNameSpace
    -> AttributeRenamer
AttributeRenamer
    ATTR_LIST = legalFoundationDate,LEGAL_FOUNDATION_DATE,legalFoundationDocumentDate,LEGAL_FOUNDATION_DOC_DATE,legalFoundationDocumentTitle,LEGAL_FOUNDATION_DOC_TITLE,siteName,NOME_SITO,localId,ID
    -> ProtectedSite (writer GML_1)
ProtectedSite (writer GML_1)
    attributes: idNameSpace xml_char(20), localId xml_char(20), applicationSchema xml_char(20), legalFoundationDocumentTitle xml_char(20), legalFoundationDocumentDate xml_char(20), siteDesignationList{}.DESIGNATION_SCHEMA xml_char(20), siteDesignationList{}.DESIGNATION xml_char(20), siteDesignationList{}.PERCENTUALE xml_char(20), siteName xml_char(20), siteClassificationList{}.CLASSIFICATION xml_char(20), legalFoundationDate xml_char(20)
